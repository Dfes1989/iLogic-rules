' <FireOthersImmediately>False</FireOthersImmediately>
oCurrentScale = ThisApplication.ActiveDocument.ActiveSheet.DrawingViews.Item(1).Scale
Dim oScale As String = InputBox("Enter new scale", "ilogic", oCurrentScale) 
If (Not String.IsNullOrWhiteSpace(oScale)) Then 
oScale = ThisApplication.UnitsOfMeasure.GetValueFromExpression(oScale, UnitsTypeEnum.kUnitlessUnits) 
End If 
For Each oView In ThisApplication.ActiveDocument.ActiveSheet.DrawingViews 
If oView.ScaleFromBase = False Then 
oView.Scale = oScale 
End If 
Next
