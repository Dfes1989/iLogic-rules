' <FireOthersImmediately>False</FireOthersImmediately>
Sub Main()
    ' Get the active drawing document
    Dim oDoc As DrawingDocument
    oDoc = ThisApplication.ActiveDocument

    ' Index variable for drawing views
    Dim i As Integer = 1

    ' Get the active sheet
    Dim oSheet As Sheet
    oSheet = oDoc.ActiveSheet

    ' Loop through all drawing views on the active sheet
    For Each oDrawView In oSheet.DrawingViews
        ' Get the current drawing view
        Dim oView As DrawingView
        oView = oSheet.DrawingViews.Item(i)

        ' Ask the user if they want to apply the change to the current view
        Dim result As Integer
        result = MessageBox.Show("Do you want to apply the 'Show Hidden Lines' view style to the view: " & oView.Name & "?", _
                                 "Apply Hidden Line Style", MessageBoxButtons.YesNo, MessageBoxIcon.Question)

        ' If the user clicks "Yes", apply the hidden line style
        If result = DialogResult.Yes Then
            oView.ViewStyle = DrawingViewStyleEnum.kHiddenLineDrawingViewStyle
        End If

        ' Increment the index
        i = i + 1
    Next

    ' Notify the user that the operation has completed
    MessageBox.Show("Operation complete. The 'Show Hidden Lines' view style has been applied to the selected views.", _
                    "Operation Complete", MessageBoxButtons.OK, MessageBoxIcon.Information)
End Sub
