Sub Main()
    ' Ensure we are in an Assembly document
    If ThisApplication.ActiveDocumentType <> DocumentTypeEnum.kAssemblyDocumentObject Then
        MessageBox.Show("Please open an Assembly document before running this rule.", "Wrong Document Type")
        Return
    End If

    Dim oDoc As AssemblyDocument = ThisApplication.ActiveDocument
    Dim oDef As AssemblyComponentDefinition = oDoc.ComponentDefinition
    Dim reps As DesignViewRepresentations = oDef.RepresentationsManager.DesignViewRepresentations

    ' Find the "Default" representation
    Dim defaultRep As DesignViewRepresentation = Nothing
    For Each rep As DesignViewRepresentation In reps
        If rep.Name = "Default" Then
            defaultRep = rep
            Exit For
        End If
    Next

    If defaultRep Is Nothing Then
        MessageBox.Show("No Design View Representation named 'Default' found.", "Not Found")
        Return
    End If

    ' Activate Default to capture appearances
    defaultRep.Activate()

    ' Store appearances for each occurrence in Default
    Dim occs As ComponentOccurrences = oDef.Occurrences
    Dim occApps As New Dictionary(Of String, Object)

    For Each occ As ComponentOccurrence In occs
        Try
            occApps(occ.Name) = occ.Appearance
        Catch
            ' Some occurrences may not have explicit appearances
        End Try
    Next

    ' Apply stored appearances to every other Design View Rep
    Dim repsProcessed As Integer = 0
    Dim totalAssignments As Integer = 0

    For Each rep As DesignViewRepresentation In reps
        If rep.Name <> "Default" Then
            Try
                rep.Activate()

                For Each occ As ComponentOccurrence In occs
                    If occApps.ContainsKey(occ.Name) Then
                        Try
                            occ.Appearance = occApps(occ.Name)
                            totalAssignments += 1
                        Catch
                            ' Ignore failures
                        End Try
                    End If
                Next

                oDoc.Update()
                repsProcessed += 1
            Catch
                ' Skip if activation fails
            End Try
        End If
    Next

    ' Return to Default rep
    defaultRep.Activate()
    oDoc.Update()

    MessageBox.Show("Processed " & repsProcessed.ToString() & " representation(s)." & vbCrLf &
                    "Total occurrence appearance assignments: " & totalAssignments.ToString(), "Done")
End Sub
